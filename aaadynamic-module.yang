module ietf-mud{
        container mud{
            leaf mud-version{
                type uint8;
            }
            leaf mud-url{
                type inet:uri;
            }
            leaf mud-signature{
                type inet:uri;
            }
            leaf last-update{
                type yang:date-and-time;
            }
            leaf cache-validity{
                type uint8;
            }
            leaf is-supported{
                type boolean;
            }
            leaf-list systeminfo{
                type string;
            }
            leaf mfg-name{
                type string;
            }
            leaf model-name{
                type string;
            }
            leaf firmware-rev{
                type string;
            }
            leaf software-rev{
                type string;
            }
            leaf documentation{
                type inet:uri;
            }
            leaf extensions*{
                type string;
            }
            container from-device-policy{
                leaf-list acls*{
                    leaf name{
                        type string;
                    }
                }
            }
            container to-device-policy{
                leaf-list acl-name{
                    type string;
                }
            }
        }
    }
